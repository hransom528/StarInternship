# ACSRequirements

## #1: Attitude Control Modes (Functional)
The CubeSat shall have control logic that can be turned off or on from an input

## #2: Sun Tracking (Container)

### #3: Enter Sun Tracking from Transition (Functional)
Sun tracking shall be entered from Transition when navigation has set to Sun tracking

### #4: Output upon entering Sun Tracking (Functional)
The controller shall output a signal that indicates entering the sun tracking state

### #16: Attitude Error Output (Functional)
The attitude error relative to a sun tracking position shall be calculated and output

## #5: Nadir Pointing (Container)

### #6: Enter Nadir Pointing from Transition (Functional)
Nadir Pointing shall be entered from Transition when navigation has set to Nadir Pointing

### #7: Output upon entering Nadir Pointing (Functional)
The controller shall output a signal that indicates entering the Nadir Pointing mode

### #17: Attitude Error Output (Functional)
The attitude error relative to a nadir pointing position shall be calculated and output

## #8: Off Mode (Container)

### #10: Enter Off (Functional)
Off mode shall be entered when initializing the controller or when navigation has been set to off

### #11: Output upon entering Off Mode (Functional)
The controller shall output a signal that indicates entering Off mode

### #12: Output in Off Mode (Functional)
The controller shall output zero torque commands for all 3 axes

## #9: On Mode (Container)

### #13: Enter On (Functional)
On mode shall be entered when navigation has been set to Sun tracking mode or Nadir Pointing mode

### #14: Output upon entering On Mode (Functional)
The controller shall output a signal that indicates entering On mode

### #15: States of On mode (Functional)
One of three states shall be active when in On mode
- Transition
- Sun Tracking
- Nadir Pointing (Earth)

## #18: Transition (Container)

### #19: Enter Transition from Sun Tracking (Functional)
Transition mode shall be entered from Sun Tracking when navigation has set to Nadir Pointing

### #20: Enter Transition from Nadir Pointing (Functional)
Transition state shall be entered from Nadir Pointing when navigation has set to Sun Tracking

### #21: Enter Transition for Initializing On mode (Functional)
Transition state shall be entered when first entering On mode

## #22: Torque Command (Functional)
A controller shall calculate torque commands based on the attitude error and navigation mode
