# SystemRequirements

## #1: Provide visual imagery (Functional)
The system shall provide and store visual imagery of MathWorks headquarters [42.2775 N, 71.2468 W] 1 times daily at 10 meters resolution.

### #2: Visual imagery collection (Functional)
The satellite shall provide for collection by the ground system visual imagery of MathWorks headquarters 1 times daily at 10 meters resolution.

#### #10: Orbit Selection (Functional)
The Cubesat shall have ground coverage of [ 42.2775 N, 71.2468 W]

#### #11: CubeSat (Functional)
The cubesat shall provide for collection by the ground system visual imagery of MathWorks headquarters 1 times daily at 10 meters resolution.

##### #4: Imaging payload performance (Functional)
The imaging payload shall collect visual imagery at TBD2 meters resolution from a distance of TBD3 km with atmospheric conditions as specified in TBS1.

##### #5: GNC pointing accuracy (Functional)
The GNC system shall point the imaging payload at a specified ground coordinate location with accuracy of TBD4 degrees.

##### #6: GNC slew rate (Functional)
The attitude control subsystem shall be capable of slewing the spacecraft at TBD8 deg/sec.

##### #7: Image downlink (Functional)
The communications subsystem shall downlink visual imagery to the ground.

##### #8: On-board image management (Functional)
The CDHS shall collect visual imagery from the imaging payload and store it for ground downlink.

##### #23: Power for on-board imaging tasks (Functional)
The electrical power system shall provide power to bus and imaging payload equipment accounting for eclipse durations of [eclipseDuration:TBD6] minutes per [orbitTime:TBD7] minute orbit.

###### #24: Power System Control (Functional)
The Power System shall be able to control the power of the CubeSat.

###### #25: Power System Plant (Functional)
The Power System shall contain both a solar array system for energy generation

###### #26: Solar Panel (Functional)
The Solar Panel shall generate power using a grid of photovoltaic cells

###### #28: Solar Panel Cells (Functional)
The Solar Panel Cells shall generate [PVPowerGen:3] W

###### #27: Battery (Functional)
The battery sahll be created from a grid of battery cells.

###### #29: Battery Cell (Functional)
The Battery cells shall be the main energy storage device

### #3: Visual imagery ground storage (Functional)
The ground segment shall collect and store visual imagery provided by the satellite.
